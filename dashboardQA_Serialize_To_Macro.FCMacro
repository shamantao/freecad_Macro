import FreeCAD as App
import Part
import Sketcher
import PartDesign
import os

# ==============================================================================
# Serialize_To_Macro.FCMacro
# ==============================================================================
# This macro analyzes the active FreeCAD document and generates a Python script
# capable of rebuilding the project structure and geometry from scratch.
# Ideally suited for "cleaning" a project or sharing a parametric model definition.
# ==============================================================================

def get_output_path(doc):
    """Generates the output file path based on the document name."""
    clean_name = doc.Name.replace(" ", "_").replace("-", "_")
    filename = f"rebuild_{clean_name}.py"
    
    if doc.FileName:
        return os.path.join(os.path.dirname(doc.FileName), filename)
    else:
        return os.path.join(os.path.expanduser("~"), filename)

def export_placement(obj, var_name):
    p = obj.Placement.Base
    r = obj.Placement.Rotation
    axis = r.Axis
    angle = r.Angle * 180.0 / 3.1415926535
    return f"{var_name}.Placement = App.Placement(App.Vector({p.x:.2f}, {p.y:.2f}, {p.z:.2f}), App.Rotation(App.Vector({axis.x:.2f}, {axis.y:.2f}, {axis.z:.2f}), {angle:.2f}))\n"

def export_view(obj, var_name):
    if not hasattr(obj, "ViewObject") or not obj.ViewObject:
        return ""
    lines = []
    
    # Color
    if hasattr(obj.ViewObject, "ShapeColor"):
        c = obj.ViewObject.ShapeColor
        lines.append(f"if hasattr({var_name}.ViewObject, 'ShapeColor'): {var_name}.ViewObject.ShapeColor = ({c[0]:.2f}, {c[1]:.2f}, {c[2]:.2f})")
    
    # Transparency
    if hasattr(obj.ViewObject, "Transparency"):
        t = obj.ViewObject.Transparency
        if t > 0:
            lines.append(f"if hasattr({var_name}.ViewObject, 'Transparency'): {var_name}.ViewObject.Transparency = {t}")
    
    # Visibility
    if not obj.ViewObject.Visibility:
         lines.append(f"if hasattr({var_name}.ViewObject, 'Visibility'): {var_name}.ViewObject.Visibility = False")
    
    return "\n".join(lines) + "\n"

def export_sketch(obj, var_name, body_var):
    lines = []
    lines.append(f"# --- Sketch: {obj.Name} ---")
    lines.append(f"{var_name} = {body_var}.newObject('Sketcher::SketchObject', '{obj.Name}')")
    
    # Use the helper function for robust attachment
    lines.append(f"attach_sketch({var_name}, App.ActiveDocument.XY_Plane)")
    
    # GEOMETRY
    for i, g in enumerate(obj.Geometry):
        if isinstance(g, Part.LineSegment):
            lines.append(f"{var_name}.addGeometry(Part.LineSegment(App.Vector({g.StartPoint.x:.5f},{g.StartPoint.y:.5f},0), App.Vector({g.EndPoint.x:.5f},{g.EndPoint.y:.5f},0)), False)")
        elif isinstance(g, Part.Circle):
            center = g.Center
            radius = g.Radius
            lines.append(f"{var_name}.addGeometry(Part.Circle(App.Vector({center.x:.5f},{center.y:.5f},0), App.Vector(0,0,1), {radius:.5f}), False)")
        # TODO: Add ArcOfCircle, etc.

    # CONSTRAINTS
    # We attempt to replicate constraints. 
    # Note: Indices in FreeCAD Sketches correspond to the order of addGeometry.
    for c in obj.Constraints:
        args = f"'{c.Type}'"
        
        # Standardize constraints arguments mapping
        # 1. Constraints with alignment (Coincident, Tangent...)
        if c.Type in ["Coincident", "Tangent", "Perpendicular", "Parallel", "Equal", "Symmetric"]:
            args += f", {c.First}, {c.FirstPos}, {c.Second}, {c.SecondPos}"
        
        # 2. Vertical/Horizontal/Block/Fixed
        elif c.Type in ["Vertical", "Horizontal", "Block", "Fxied"]:
             args += f", {c.First}" 
             # Some versions need pos? Usually not for lines.
        
        # 3. Dimnesional (Distance, Radius...)
        elif c.Type in ["Distance", "DistanceX", "DistanceY", "Radius", "Diameter", "Angle"]:
             if c.Second == -2000: # Single geometry (e.g. Radius)
                  args += f", {c.First}, {c.Value}"
             else: # Between two points
                  args += f", {c.First}, {c.FirstPos}, {c.Second}, {c.SecondPos}, {c.Value}"
        
        lines.append(f"# {var_name}.addConstraint(Sketcher.Constraint({args}))")
        
    return "\n".join(lines) + "\n"

def run():
    doc = App.ActiveDocument
    if not doc:
        App.Console.PrintError("Aucun document actif.\n")
        return

    out_path = get_output_path(doc)
    doc_new_name = doc.Name + "_Rebuild"
    
    with open(out_path, "w", encoding="utf-8") as f:
        import datetime
        timestamp = datetime.datetime.now().strftime("%Y-%m-%d %H:%M:%S")
        f.write("# Auto-generated Reconstruction Script\n")
        f.write("# Generated by: Serialize_To_Macro (Community Edition)\n")
        f.write(f"# Date: {timestamp}\n")
        f.write("# Target: FreeCAD 1.0.2+\n")
        f.write("import FreeCAD as App\n")
        f.write("import Part\n")
        f.write("import Sketcher\n")
        f.write("import PartDesign\n\n")
        
        # Helper function for robust attachment
        f.write("def attach_sketch(sketch, plane):\n")
        f.write("    if hasattr(sketch, 'AttachmentSupport'):\n")
        f.write("        sketch.AttachmentSupport = [(plane, '')]\n")
        f.write("    elif hasattr(sketch, 'Support'):\n")
        f.write("        sketch.Support = (plane, [''])\n")
        f.write("    if hasattr(sketch, 'MapMode'):\n")
        f.write("        sketch.MapMode = 'FlatFace'\n\n")

        f.write(f"DOC_NAME = '{doc_new_name}'\n")
        f.write("if App.ActiveDocument and App.ActiveDocument.Name == DOC_NAME:\n")
        f.write("    App.closeDocument(DOC_NAME)\n")
        f.write("doc = App.newDocument(DOC_NAME)\n")
        f.write("App.setActiveDocument(DOC_NAME)\n\n")
        
        # --- ITERATION ---
        # We iterate over top-level objects only to maintain hierarchy logic where possible
        
        for obj in doc.Objects:
            clean_name = obj.Name.replace(" ", "_").replace("-", "_")
            if not clean_name.isidentifier():
                clean_name = "Obj_" + clean_name
            
            # --- BODY ---
            if obj.TypeId == "PartDesign::Body":
                f.write(f"# --- BODY: {obj.Label} ---\n")
                f.write(f"{clean_name} = doc.addObject('PartDesign::Body', '{obj.Name}')\n")
                f.write(export_placement(obj, clean_name))
                f.write(export_view(obj, clean_name))
                
                # Children
                if hasattr(obj, "Group"):
                    for child in obj.Group:
                        c_name = child.Name.replace(" ", "_").replace("-", "_")
                        if not c_name.isidentifier(): c_name = "Obj_" + c_name
                        
                        if child.TypeId == "Sketcher::SketchObject":
                            f.write(export_sketch(child, c_name, clean_name))
                            
                        elif child.TypeId == "PartDesign::Pad":
                            f.write(f"{c_name} = {clean_name}.newObject('PartDesign::Pad', '{child.Name}')\n")
                            if child.Profile:
                                # Profile can be a single object, a list, or a tuple
                                prof = child.Profile
                                if isinstance(prof, (list, tuple)):
                                    prof = prof[0]
                                f.write(f"{c_name}.Profile = doc.getObject('{prof.Name}')\n")
                            f.write(f"{c_name}.Length = {child.Length.Value:.4f}\n")
                            f.write(export_view(child, c_name))
                            
                        elif child.TypeId == "PartDesign::Pocket":
                            f.write(f"{c_name} = {clean_name}.newObject('PartDesign::Pocket', '{child.Name}')\n")
                            if child.Profile:
                                prof = child.Profile
                                if isinstance(prof, (list, tuple)):
                                    prof = prof[0]
                                f.write(f"{c_name}.Profile = doc.getObject('{prof.Name}')\n")
                            f.write(f"{c_name}.Length = {child.Length.Value:.4f}\n")
                            f.write(f"{c_name}.Reversed = {child.Reversed}\n")
                            f.write(export_view(child, c_name))

            # --- PART / GROUP ---
            elif obj.TypeId == "App::Part": 
                f.write(f"# --- PART: {obj.Label} ---\n")
                f.write(f"{clean_name} = doc.addObject('App::Part', '{obj.Name}')\n")
                f.write(export_placement(obj, clean_name))
                
                if hasattr(obj, "Group"):
                    for child in obj.Group:
                        c_name = child.Name.replace(" ", "_").replace("-", "_")
                        # Recurse for basic primitives
                        if child.TypeId == "Part::Cylinder":
                             f.write(f"{c_name} = doc.addObject('Part::Cylinder', '{child.Name}')\n")
                             f.write(f"{c_name}.Radius = {child.Radius.Value:.4f}\n")
                             f.write(f"{c_name}.Height = {child.Height.Value:.4f}\n")
                             f.write(export_placement(child, c_name))
                             f.write(f"{clean_name}.addObject({c_name})\n")

        f.write("\nApp.ActiveDocument.recompute()\n")
        f.write("Gui.SendMsgToActiveView('ViewFit')\n")
        f.write("print('Reconstruction terminée.')\n")
        
    App.Console.PrintMessage(f"Macro de sauvegarde générée : {out_path}\n")
    print(f"Script de reconstruction créé : {out_path}")

if __name__ == "__main__":
    run()
