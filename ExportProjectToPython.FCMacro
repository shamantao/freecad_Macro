#!/usr/bin/env python
# -*- coding: utf-8 -*-
"""
ExportProjectToPython.FCMacro

This FreeCAD macro exports the entire active project to a Python script.
The generated Python code can be used to recreate the project from scratch,
making it useful for forking, version control, and collaborative development.

Usage:
1. Open a FreeCAD document
2. Run this macro from Macro > Macros > Execute
3. Select a save location for the generated .py file

Author: Generated with GitHub Copilot
License: GPL-3.0
"""

import FreeCAD as App
import FreeCADGui as Gui
from PySide import QtGui
import os
import datetime


def get_object_creation_code(obj):
    """
    Generate Python code to recreate a FreeCAD object.
    
    Args:
        obj: FreeCAD document object
        
    Returns:
        String containing Python code
    """
    code_lines = []
    
    # Add comment with object info
    code_lines.append(f"\n# Creating object: {obj.Label} (Type: {obj.TypeId})")
    
    # Handle different object types
    if obj.TypeId == "PartDesign::Body":
        code_lines.append(f"{obj.Name} = doc.addObject('PartDesign::Body', '{obj.Label}')")
    elif obj.TypeId == "Part::Box":
        code_lines.append(f"{obj.Name} = doc.addObject('Part::Box', '{obj.Label}')")
        code_lines.append(f"{obj.Name}.Length = {obj.Length}")
        code_lines.append(f"{obj.Name}.Width = {obj.Width}")
        code_lines.append(f"{obj.Name}.Height = {obj.Height}")
    elif obj.TypeId == "Part::Cylinder":
        code_lines.append(f"{obj.Name} = doc.addObject('Part::Cylinder', '{obj.Label}')")
        code_lines.append(f"{obj.Name}.Radius = {obj.Radius}")
        code_lines.append(f"{obj.Name}.Height = {obj.Height}")
    elif obj.TypeId == "Part::Sphere":
        code_lines.append(f"{obj.Name} = doc.addObject('Part::Sphere', '{obj.Label}')")
        code_lines.append(f"{obj.Name}.Radius = {obj.Radius}")
    elif obj.TypeId == "Part::Cone":
        code_lines.append(f"{obj.Name} = doc.addObject('Part::Cone', '{obj.Label}')")
        code_lines.append(f"{obj.Name}.Radius1 = {obj.Radius1}")
        code_lines.append(f"{obj.Name}.Radius2 = {obj.Radius2}")
        code_lines.append(f"{obj.Name}.Height = {obj.Height}")
    elif obj.TypeId == "Part::Torus":
        code_lines.append(f"{obj.Name} = doc.addObject('Part::Torus', '{obj.Label}')")
        code_lines.append(f"{obj.Name}.Radius1 = {obj.Radius1}")
        code_lines.append(f"{obj.Name}.Radius2 = {obj.Radius2}")
    elif obj.TypeId == "Sketcher::SketchObject":
        code_lines.append(f"{obj.Name} = doc.addObject('Sketcher::SketchObject', '{obj.Label}')")
        # Note: Sketch geometry would need detailed export - simplified here
        code_lines.append(f"# TODO: Add sketch geometry for {obj.Label}")
    elif obj.TypeId.startswith("PartDesign::"):
        # Handle PartDesign features
        feature_type = obj.TypeId.replace("PartDesign::", "")
        code_lines.append(f"{obj.Name} = doc.addObject('{obj.TypeId}', '{obj.Label}')")
    else:
        # Generic object creation
        code_lines.append(f"{obj.Name} = doc.addObject('{obj.TypeId}', '{obj.Label}')")
    
    # Set placement
    if hasattr(obj, 'Placement'):
        placement = obj.Placement
        base = placement.Base
        rotation = placement.Rotation
        code_lines.append(f"{obj.Name}.Placement = App.Placement(")
        code_lines.append(f"    App.Vector({base.x}, {base.y}, {base.z}),")
        code_lines.append(f"    App.Rotation({rotation.Q[0]}, {rotation.Q[1]}, {rotation.Q[2]}, {rotation.Q[3]})")
        code_lines.append(f")")
    
    # Set visibility
    if hasattr(obj, 'ViewObject') and obj.ViewObject:
        code_lines.append(f"{obj.Name}.ViewObject.Visibility = {obj.ViewObject.Visibility}")
    
    # Set common properties
    for prop_name in obj.PropertiesList:
        # Skip some properties that shouldn't be set directly
        skip_props = ['Shape', 'Proxy', 'ExpressionEngine', 'Label2', 'Placement']
        if prop_name in skip_props:
            continue
            
        try:
            prop_value = getattr(obj, prop_name)
            # Handle different property types
            if isinstance(prop_value, (int, float, bool)):
                code_lines.append(f"# {obj.Name}.{prop_name} = {prop_value}")
            elif isinstance(prop_value, str):
                code_lines.append(f"# {obj.Name}.{prop_name} = '{prop_value}'")
        except:
            pass
    
    return "\n".join(code_lines)


def export_project_to_python():
    """
    Main function to export the current FreeCAD document to Python code.
    """
    doc = App.ActiveDocument
    
    if doc is None:
        QtGui.QMessageBox.warning(
            None,
            "No Active Document",
            "Please open a FreeCAD document before running this macro."
        )
        return
    
    # Ask user for save location
    file_dialog = QtGui.QFileDialog()
    file_path, _ = file_dialog.getSaveFileName(
        None,
        "Save Python Export",
        os.path.join(os.path.expanduser("~"), f"{doc.Name}_export.py"),
        "Python Files (*.py)"
    )
    
    if not file_path:
        return  # User cancelled
    
    # Start building the Python code
    code = []
    code.append("#!/usr/bin/env python")
    code.append("# -*- coding: utf-8 -*-")
    code.append('"""')
    code.append(f"FreeCAD Project Export: {doc.Name}")
    code.append(f"Generated on: {datetime.datetime.now().strftime('%Y-%m-%d %H:%M:%S')}")
    code.append(f"Original file: {doc.FileName if doc.FileName else 'Unsaved document'}")
    code.append("")
    code.append("This script recreates the FreeCAD project programmatically.")
    code.append('"""')
    code.append("")
    code.append("import FreeCAD as App")
    code.append("import Part")
    code.append("import PartDesign")
    code.append("import Sketcher")
    code.append("")
    code.append("# Create new document")
    code.append(f"doc = App.newDocument('{doc.Name}')")
    code.append("")
    
    # Add document properties
    code.append("# Document properties")
    code.append(f"doc.Label = '{doc.Label}'")
    if hasattr(doc, 'Comment'):
        code.append(f"doc.Comment = '''{doc.Comment}'''")
    if hasattr(doc, 'Company'):
        code.append(f"doc.Company = '{doc.Company}'")
    if hasattr(doc, 'Author'):
        code.append(f"doc.Author = '{doc.Author}'")
    code.append("")
    
    # Export all objects
    code.append("# Create objects")
    for obj in doc.Objects:
        try:
            obj_code = get_object_creation_code(obj)
            code.append(obj_code)
        except Exception as e:
            code.append(f"\n# Error exporting {obj.Label}: {str(e)}")
    
    # Recompute document
    code.append("\n# Recompute document")
    code.append("doc.recompute()")
    code.append("")
    code.append("# Save document (optional)")
    code.append("# doc.saveAs('path/to/save/document.FCStd')")
    code.append("")
    code.append("print('Project recreated successfully!')")
    
    # Write to file
    try:
        with open(file_path, 'w', encoding='utf-8') as f:
            f.write("\n".join(code))
        
        QtGui.QMessageBox.information(
            None,
            "Export Complete",
            f"Project exported successfully to:\n{file_path}\n\n"
            f"Exported {len(doc.Objects)} objects."
        )
        
        # Ask if user wants to open the file
        reply = QtGui.QMessageBox.question(
            None,
            "Open File",
            "Do you want to open the exported Python file?",
            QtGui.QMessageBox.Yes | QtGui.QMessageBox.No
        )
        
        if reply == QtGui.QMessageBox.Yes:
            if os.name == 'nt':  # Windows
                os.startfile(file_path)
            elif os.name == 'posix':  # Linux/Mac
                import subprocess
                subprocess.run(['xdg-open', file_path])
                
    except Exception as e:
        QtGui.QMessageBox.critical(
            None,
            "Export Error",
            f"Failed to export project:\n{str(e)}"
        )


# Run the export
if __name__ == "__main__":
    export_project_to_python()
